module hello {
    yang-version 1;
    namespace "urn:opendaylight:params:xml:ns:yang:hello";
    prefix "hello";
    
    import yang-ext {prefix ext; revision-date "2013-07-09";}

    revision "2015-01-05" {
        description "Initial revision of hello model";
    }
    
    typedef node-type {
        type enumeration {
            enum otn;
            enum ptn;
            enum roadm;
        }
    }
    
    typedef node-id {
        type string;
        description "Identifier for a particular node";
    }
    
    grouping node {

        leaf id {
            type node-id;
            description "The unique identifier for the node.";
        }
        leaf type {
            type node-type;
        }
    }
    
    container nodes {

        description "The root container of all nodes.";

        list node {
            key "id";
            ext:context-instance "node-context";
            uses node; 
        }
    }
    
    typedef node-ref {
        type instance-identifier;
        description "A reference that points to an nodes/node in the data tree.";
    }
    
    identity node-context {
        description "A node-context is a classifier for node elements which allows an RPC to provide a service on behalf of a particular element in the data tree.";
    }
    
    rpc node-update {
    
    }
    
    rpc rpc-inputtest {
    	input {
    		leaf strin {
    			type string;
    		}
    	}
    }
    
    rpc routedrpc-test {
    	input {
    		leaf node-ref {
    			ext:context-reference "node-context";
            	type node-ref;
    		}
    	}
    }
}
